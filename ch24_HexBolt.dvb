Attribute VB_Name = "basHexBolt"
Sub HexBolt()
  frmHexBolt.show
End Sub

Attribute VB_Name = "frmHexBolt"
Attribute VB_Base = "0{A9077447-FA73-4AF0-9744-9600A6A8D6D8}{22B3CC8D-6435-4EFD-B2EA-AC8012DEB8DA}"
Attribute VB_GlobalNameSpace = False
Attribute VB_Creatable = False
Attribute VB_PredeclaredId = True
Attribute VB_Exposed = False
Attribute VB_TemplateDerived = False
Attribute VB_Customizable = False
' Define a multi-value array
Dim hexBoltArray(0 To 9, 1 To 5)
Dim selectedIndex As Integer
Const PI As Double = 3.14159

Private Sub cmdCancel_Click()
  End
End Sub

Private Sub cmdInsert_Click()
  If (CDbl(currentText) < 1 Or CDbl(currentText) > 8) And Me.lstDiameter.Text <> "" Then
    Me.Hide
    
    If Me.optTop.Value = True Then
      drawBoltTop
    Else
      drawBoltSide
    End If
    
    Me.show
  Else
    MsgBox "Select a bolt or enter valid bolt length."
  End If
End Sub

Private Sub imgSide_Click()
  optSide.Value = True
End Sub

Private Sub imgTop_Click()
  optTop.Value = True
End Sub

Private Sub lstDiameter_Click()
  selectedIndex = Me.lstDiameter.ListIndex
  
  ' Display the head size of the bolt
  Me.txtHeadSize = hexBoltArray(selectedIndex, 3)
  
  ' Display thread length of the bolt
  Me.txtTL6OrLess = hexBoltArray(selectedIndex, 4)
  Me.txtTL6OrMore = hexBoltArray(selectedIndex, 4) + 0.25
End Sub

Private Sub SpinButton1_SpinDown()
  Me.txtLength.Text = Format(Me.txtLength.Text - 0.0625, "0.00000")
End Sub

Private Sub SpinButton1_SpinUp()
  Me.txtLength.Text = Format(Me.txtLength.Text + 0.0625, "0.00000")
End Sub

Private Sub txtLength_Change()
  Dim currentText As String
  currentText = Me.txtLength.Text
  
  If currentText = "" Then currentText = "0"
  
  If CDbl(currentText) < 1 Or CDbl(currentText) > 8 Then
    Me.cmdInsert.Enabled = False
    Me.txtLength.BackColor = &HC0FFFF
  Else
    Me.cmdInsert.Enabled = True
    Me.txtLength.BackColor = &H80000005
  End If
End Sub

Private Sub txtLength_KeyPress(ByVal KeyAscii As MSForms.ReturnInteger)
  Dim currentText As String
  currentText = Me.txtLength.Text
  
  Select Case KeyAscii
     Case Asc("0") To Asc("9")
     Case Asc(".")
         If InStr(1, currentText, ".") > 0 Then
             KeyAscii = 0
         End If
     Case Else
         KeyAscii = 0
  End Select
End Sub

Private Sub UserForm_Initialize()
  ' Populate list box with bolt sizes
  ' Diameter (Display)         ' Diameter value             ' Head Size                  ' Thread length for 6" or < ' Head height
  hexBoltArray(0, 1) = "1/4":  hexBoltArray(0, 2) = 0.25:   hexBoltArray(0, 3) = 0.4375: hexBoltArray(0, 4) = 0.75:  hexBoltArray(0, 5) = 0.1719
  hexBoltArray(1, 1) = "5/16": hexBoltArray(1, 2) = 0.3125: hexBoltArray(1, 3) = 0.5:    hexBoltArray(1, 4) = 0.875: hexBoltArray(1, 5) = 0.2188
  hexBoltArray(2, 1) = "3/8":  hexBoltArray(2, 2) = 0.375:  hexBoltArray(2, 3) = 0.5625: hexBoltArray(2, 4) = 1#:    hexBoltArray(2, 5) = 0.25
  hexBoltArray(3, 1) = "7/16": hexBoltArray(3, 2) = 0.4375: hexBoltArray(3, 3) = 0.625:  hexBoltArray(3, 4) = 1.125: hexBoltArray(3, 5) = 0.2969
  hexBoltArray(4, 1) = "1/2":  hexBoltArray(4, 2) = 0.5:    hexBoltArray(4, 3) = 0.75:   hexBoltArray(4, 4) = 1.25:  hexBoltArray(4, 5) = 0.3438
  hexBoltArray(5, 1) = "9/16": hexBoltArray(5, 2) = 0.5625: hexBoltArray(5, 3) = 0.8125: hexBoltArray(5, 4) = 1.375: hexBoltArray(5, 5) = 0.3829
  hexBoltArray(6, 1) = "5/8":  hexBoltArray(6, 2) = 0.625:  hexBoltArray(6, 3) = 0.9375: hexBoltArray(6, 4) = 1.5:   hexBoltArray(6, 5) = 0.4219
  hexBoltArray(7, 1) = "3/4":  hexBoltArray(7, 2) = 0.75:   hexBoltArray(7, 3) = 1.125:  hexBoltArray(7, 4) = 1.75:  hexBoltArray(7, 5) = 0.5
  hexBoltArray(8, 1) = "7/8":  hexBoltArray(8, 2) = 0.875:  hexBoltArray(8, 3) = 1.3125: hexBoltArray(8, 4) = 2:     hexBoltArray(8, 5) = 0.5781
  hexBoltArray(9, 1) = "1":    hexBoltArray(9, 2) = 1#:     hexBoltArray(9, 3) = 1.5:    hexBoltArray(9, 4) = 2.25:  hexBoltArray(9, 5) = 0.6719
  
  Me.lstDiameter.Clear
  Me.lstDiameter.List = hexBoltArray
  
  ' Set the default length
  Me.txtLength = "1.00000"
  
  On Error Resume Next
  
  ' Add the preview images
  Me.imgTop.Picture = LoadPicture("hexbolt_top.jpg")
  Me.imgSide.Picture = LoadPicture("hexbolt_side.jpg")
End Sub

Private Sub drawBoltTop()
  ' Set up layers and linetypes
  initialDrawing
  
  If ThisDrawing.ActiveSpace = acPaperSpace Then
    MsgBox "Macro only works in model space."
    
    Exit Sub
  End If
  
  On Error GoTo ErrMsg
  
  Dim pt As Variant
  pt = ThisDrawing.Utility.GetPoint(, vbLf + "Specify center of bolt head: ")
  
  Dim circObj As AcadCircle
  Set circObj = ThisDrawing.ModelSpace.AddCircle(pt, hexBoltArray(selectedIndex, 2) / 2)
  circObj.Layer = "Hidden"
  
  Dim lwPlineObj As AcadLWPolyline
  Set lwPlineObj = ThisDrawing.ModelSpace.AddLightWeightPolyline( _
                       calcCircHexTop(pt, hexBoltArray(selectedIndex, 3) / 2))
  lwPlineObj.Layer = "Bolt"
  lwPlineObj.Closed = True
  
  Exit Sub
  
ErrMsg:
  MsgBox "Invalid point provided."
End Sub

Private Sub drawBoltSide()
  ' Set up layers and linetypes
  initialDrawing
  
  If ThisDrawing.ActiveSpace = acPaperSpace Then
    MsgBox "Macro only works in model space."
    
    Exit Sub
  End If
  
  On Error GoTo ErrMsg
  
  Dim pt As Variant
  pt = ThisDrawing.Utility.GetPoint(, vbLf + "Specify middle of bolt head: ")
  
  ' Draw outline of bolt head
  Dim lwPlineObj As AcadLWPolyline
  Set lwPlineObj = ThisDrawing.ModelSpace.AddLightWeightPolyline( _
                       calcCircHexSide(pt, hexBoltArray(selectedIndex, 3) / 2, _
                       CDbl(hexBoltArray(selectedIndex, 5))))
  lwPlineObj.Layer = "Bolt"
  lwPlineObj.Closed = True
  
  ' Draw lines for visble side of head
  Dim sideLength As Double
  sideLength = Format(Tan(30 * (PI / 180)) * (hexBoltArray(selectedIndex, 3)), "0.0000")
  
  ' Start point of first line
  Dim startPt As Variant
  Dim endPt As Variant
  startPt = ThisDrawing.Utility.PolarPoint(pt, PI / 2, sideLength / 2)
  
  ' End point of first line
  endPt = ThisDrawing.Utility.PolarPoint(startPt, 0, CDbl(hexBoltArray(selectedIndex, 5)))
  
  ' Draw line
  Dim lineObj As AcadLine
  Set lineObj = ThisDrawing.ModelSpace.AddLine(startPt, endPt)
  lineObj.Layer = "Bolt"

  ' Calculate and draw second line
  startPt = ThisDrawing.Utility.PolarPoint(pt, (PI / 2) * -1, sideLength / 2)
  endPt = ThisDrawing.Utility.PolarPoint(startPt, 0, CDbl(hexBoltArray(selectedIndex, 5)))
  
  Set lineObj = ThisDrawing.ModelSpace.AddLine(startPt, endPt)
  lineObj.Layer = "Bolt"
  
  ' Draw thread outline of bolt
  Set lwPlineObj = ThisDrawing.ModelSpace.AddLightWeightPolyline( _
                       calcCircHexSideThread(pt, hexBoltArray(selectedIndex, 2) / 2, _
                       Me.txtLength, CDbl(hexBoltArray(selectedIndex, 5))))
  lwPlineObj.Layer = "Bolt"
  lwPlineObj.Closed = False
    

  ' Calculate and draw center line
  startPt = ThisDrawing.Utility.PolarPoint(pt, PI, sideLength / 2)
  endPt = ThisDrawing.Utility.PolarPoint(startPt, 0, CDbl(hexBoltArray(selectedIndex, 5) + Me.txtLength + sideLength))
  
  Set lineObj = ThisDrawing.ModelSpace.AddLine(startPt, endPt)
  lineObj.Layer = "Center"
  
  Exit Sub
  
ErrMsg:

End Sub

Private Sub initialDrawing()
  ' Load the Center and Hidden linetypes
  loadLinetype "Center"
  loadLinetype "Hidden"
  
  Dim layObj As AcadLayer
  
  ' Create the Center layer
  createLayer "Center", "Center", acGreen
  
  ' Create the Hidden layer
  createLayer "Hidden", "Hidden", acMagenta
  
  ' Create the Bolt layer
  createLayer "Bolt", , acBlue
  
  ' Set LTSCALE to 0.25
  ThisDrawing.SetVariable "LTSCALE", 0.25
End Sub

Private Sub loadLinetype(linetypeName As String)
  On Error Resume Next
  
  ' Check to see if the linetype is already loaded
  If Not IsObject(ThisDrawing.Linetypes.Item(linetypeName)) Then ThisDrawing.Linetypes.Load linetypeName, "acad.lin"
End Sub

Private Sub createLayer(layerName As String, Optional linetypeName As String = "Continuous", Optional color As ACAD_COLOR = acWhite)
  On Error Resume Next
  
  ' Check to see if the layer exists before creating it
  If Not IsObject(ThisDrawing.Layers.Item(layerName)) Then
    Set layObj = ThisDrawing.Layers.Add(layerName)
    layObj.color = color
    layObj.Linetype = linetypeName
  End If
End Sub

Private Function calcCircHexTop(centerPoint As Variant, radius As Double) As Variant
  Dim sideLength As Double
  sideLength = Format(Tan(30 * (PI / 180)) * (radius * 2), "0.0000")
  
  Dim pt As Variant
  Dim points(1 To 12) As Double
  
  Dim ang90 As Double
  ang90 = PI / 2
  
  Dim ang30 As Double
  ang30 = ang90 / 3
  
  Dim ang180 As Double
  ang180 = PI
  
  ' First point
  pt = ThisDrawing.Utility.PolarPoint(centerPoint, ang90, sideLength)
  points(1) = pt(0): points(2) = pt(1)
  
  ' Second point
  pt = ThisDrawing.Utility.PolarPoint(centerPoint, ang180 - ang30, sideLength)
  points(3) = pt(0): points(4) = pt(1)
  
  ' Third point
  pt = ThisDrawing.Utility.PolarPoint(centerPoint, ang180 + ang30, sideLength)
  points(5) = pt(0): points(6) = pt(1)
  
  ' Fourth point
  pt = ThisDrawing.Utility.PolarPoint(centerPoint, ang90 * -1, sideLength)
  points(7) = pt(0): points(8) = pt(1)
  
  ' Fifth point
  pt = ThisDrawing.Utility.PolarPoint(centerPoint, (ang30 * -1), sideLength)
  points(9) = pt(0): points(10) = pt(1)
  
  ' Sixth point
  pt = ThisDrawing.Utility.PolarPoint(centerPoint, ang30, sideLength)
  points(11) = pt(0): points(12) = pt(1)
  
  calcCircHexTop = points
End Function

Private Function calcCircHexSide(centerPoint As Variant, radius As Double, _
                                 headHeight As Double) As Variant
  Dim sideLength As Double
  sideLength = Format(Tan(30 * (PI / 180)) * (radius * 2), "0.0000")
  
  Dim pt As Variant
  Dim points(1 To 8) As Double
  
  Dim ang90 As Double
  ang90 = PI / 2
  
  ' First point
  pt = ThisDrawing.Utility.PolarPoint(centerPoint, ang90, sideLength)
  points(1) = pt(0): points(2) = pt(1)
  
  ' Fourth point
  pt = ThisDrawing.Utility.PolarPoint(pt, 0, headHeight)
  points(7) = pt(0): points(8) = pt(1)
  
  ' Second point
  pt = ThisDrawing.Utility.PolarPoint(centerPoint, ang90 * -1, sideLength)
  points(3) = pt(0): points(4) = pt(1)
  
  ' Third point
  pt = ThisDrawing.Utility.PolarPoint(pt, 0, headHeight)
  points(5) = pt(0): points(6) = pt(1)
  
  calcCircHexSide = points
End Function

Private Function calcCircHexSideThread(centerPoint As Variant, radius As Double, _
                                       length As Double, headHeight As Double) As Variant
  
  Dim pt As Variant
  'Dim newBasePt As Variant
  pt = ThisDrawing.Utility.PolarPoint(centerPoint, 0, headHeight)

  Dim points(1 To 8) As Double
  
  Dim ang90 As Double
  ang90 = PI / 2
  
  ' First point
  pt = ThisDrawing.Utility.PolarPoint(pt, ang90, radius)
  points(1) = pt(0): points(2) = pt(1)
  
  ' Second point
  pt = ThisDrawing.Utility.PolarPoint(pt, 0, length)
  points(3) = pt(0): points(4) = pt(1)
  
  ' Third point
  pt = ThisDrawing.Utility.PolarPoint(pt, ang90 * -1, radius * 2)
  points(5) = pt(0): points(6) = pt(1)
  
  ' Fourth point
  pt = ThisDrawing.Utility.PolarPoint(pt, PI, length)
  points(7) = pt(0): points(8) = pt(1)
  
  calcCircHexSideThread = points
End Function
